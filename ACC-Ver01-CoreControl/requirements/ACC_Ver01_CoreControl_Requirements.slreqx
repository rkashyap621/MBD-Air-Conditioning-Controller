# ACC_Ver01_CoreControl_Requirements

## ACC-REQ-001: System Initialization (Functional)
On system start, the controller shall enter the Power_Off with compressor_on = 0, fan_on = 0, fault_indicator = 0, and status outputs reset.

## ACC-REQ-002: Temperature Setpoint Input (Functional)
The controller shall use set_temperature as the desired room temperature reference for cooling control.

## ACC-REQ-003: Power ON Command (Functional)
When power_button == 1, the controller shall enter the enabled operating state, compute temperature_error = room_temperature - set_temperature, and determine cooling demand based on temperature_error and temperature_hysteresis_band.

## ACC-REQ-004: Power OFF Command (Functional)
When power_button == 0, the controller shall enter the Power_Off state and set compressor_on = 0 and fan_on = 0.

## ACC-REQ-005: Cooling Demand Activation (Functional)
If temperature_error >= temperature_hysteresis_band, the controller shall set cooling_demand = 1.

## ACC-REQ-006: Cooling Demand Deactivation (Functional)
If temperature_error <= -temperature_hysteresis_band, the controller shall set cooling_demand = 0.

## ACC-REQ-007: Compressor Minimum OFF Time (Functional)
After the compressor turns OFF, the controller shall prevent compressor restart until compressor_min_off_time has elapsed.

## ACC-REQ-008: Compressor Activation (Functional)
If cooling_demand == 1 and the compressor is not in minimum-OFF-time lockout, the controller shall set compressor_on = 1.

## ACC-REQ-009: Compressor Deactivation (Functional)
If cooling_demand == 0, power_button == 0, or a fault condition is active, the controller shall set compressor_on = 0.

## ACC-REQ-010: Fan Activation During Compressor Activation (Functional)
When compressor_on == 1, the controller shall set fan_on = 1.

## ACC-REQ-011: Fan Behavior After Compressor Deactivation (Functional)
When compressor_on == 0 after active cooling, the controller shall keep fan_on = 1 for configured fan_run_on_time, then set fan_on = 0.
