# ACC_Ver02_Operating_Modes_Requirements

## ACC-REQ-001: System Initialization (Functional)
On system start, the controller shall enter Power_Off with
cooling_demand = 0,
compressor_on = 0,
compressor_lockout = 0,
fan_on = 0,
fan_speed_cmd = 0,
and fault_indicator = 0.
Revision: Rev. 01
Change: Classification: Nil
Source Baseline: Ver. 01
Change Rationale: Nil

## ACC-REQ-002: Temperature Setpoint Input (Functional)
The controller shall use set_temperature as the desired room temperature reference for cooling control.
Revision: Rev. 01
Change: Classification: Nil
Source Baseline: Ver. 01
Change Rationale: Nil

## ACC-REQ-003: Power ON Command (Functional)
When power_button == 1, the controller shall enter Power_On, set fault_indicator = 0, update set_temperature from desired_room_temperature, and compute temperature_error = room_temperature - set_temperature. The controller shall evaluate cooling demand only while cooling control is enabled.
Revision: Rev. 02
Change: Classification: Applicability clarification
Source Baseline: Ver. 01
Change Rationale: Power_On now also contains standby and Fan-only operation.
- Rationale: Power_On now also contains standby and Fan-only operation.

## ACC-REQ-004: Power OFF Command (Functional)
When power_button == 0, the controller shall enter the Power_Off state and set compressor_on = 0 and fan_on = 0.
Revision: Rev. 01
Change: Nil
Source Baseline: Ver. 01
Change Rationale: Nil

## ACC-REQ-005: Cooling Demand Activation (Functional)
While cooling control is enabled, if temperature_error >= temperature_hysteresis_band, the controller shall set cooling_demand = 1.
Revision: Rev. 02
Change: Applicability clarification
Source Baseline: Ver. 01
Change Rationale: Cooling-demand hysteresis now applies only while cooling control is enabled.
- Rationale: Cooling-demand hysteresis now applies only while cooling control is enabled.

## ACC-REQ-006: Cooling Demand Deactivation (Functional)
While cooling control is enabled, if temperature_error <= -temperature_hysteresis_band, the controller shall set cooling_demand = 0.
Revision: Rev. 02
Change: Applicability clarification
Source Baseline: Ver. 01
Change Rationale: Cooling-demand hysteresis now applies only while cooling control is enabled.
- Rationale: Cooling-demand hysteresis now applies only while cooling control is enabled.

## ACC-REQ-007: Compressor Minimum OFF Time (Functional)
After the compressor turns OFF, the controller shall prevent compressor restart until compressor_min_off_time has elapsed.
Revision: Rev. 01
Change: Nil
Source Baseline: Ver. 01
Change Rationale: Nil

## ACC-REQ-008: Compressor Activation (Functional)
If cooling_demand == 1 and the compressor is not in minimum-OFF-time lockout, the controller shall set compressor_on = 1.
Revision: Rev. 01
Change: Nil
Source Baseline: Ver. 01
Change Rationale: Nil

## ACC-REQ-009: Compressor Deactivation (Functional)
If cooling_demand == 0, power_button == 0, or a fault condition is active, the controller shall set compressor_on = 0.
Revision: Rev. 01
Change: Nil
Source Baseline: Ver. 01
Change Rationale: Nil

## ACC-REQ-010: Fan Activation During Compressor Activation (Functional)
When compressor_on == 1, the controller shall set fan_on = 1.
Revision: Rev. 01
Change: Nil
Source Baseline: Ver. 01
Change Rationale: Nil

## ACC-REQ-011: Fan Behavior After Compressor Deactivation (Functional)
When compressor_on == 0 after active cooling, the controller shall keep fan_on = 1 for configured fan_run_on_time, then set fan_on = 0.
Revision: Rev. 01
Change: Nil
Source Baseline: Ver. 01
Change Rationale: Nil

## ACC-REQ-012: Default Power-On Standby Behavior (Functional)
When power_button == 1, no fault condition is active, and mode_enabled == 0, the controller shall activate Power_On_Standby, set cooling_demand = 0, compressor_on = 0, compressor_lockout = 0, fan_on = 1, and fan_speed_cmd = 1 corresponding to Low Speed. The controller shall set fan_only_mode_enabled = 0, cooling_mode_enabled = 0, and automatic_mode_enabled = 0.
Revision: Rev. 01
Change: New Ver. 02 requirement
Source Baseline: Ver. 02
Change Rationale: Nil

## ACC-REQ-013: Fan-Only Mode Selection and Response (Functional)
When power_button == 1, mode_enabled == 1, and mode_selected == 0, the controller shall activate Fan_Only_Mode, set fan_only_mode_enabled = 1, set cooling_mode_enabled = 0 and automatic_mode_enabled = 0, disable cooling control, set cooling_demand = 0, compressor_on = 0, compressor_lockout = 0, and keep fan_on = 1. The controller shall determine fan_speed_cmd from fan_speed_user_input.
Revision: Rev. 01
Change: New Ver. 02 requirement
Source Baseline: Ver. 02
Change Rationale: Nil

## ACC-REQ-014: Cooling Mode Selection and Response (Functional)
When power_button == 1, mode_enabled == 1, and mode_selected == 1, the controller shall activate Cooling_Mode, set cooling_mode_enabled = 1, set fan_only_mode_enabled = 0 and automatic_mode_enabled = 0, and enable the cooling-control mechanism. The controller shall determine cooling_demand using temperature_error and temperature_hysteresis_band, control the compressor using cooling demand and minimum-OFF-time protection, control the fan using compressor operation and fan run-on behavior, and determine fan_speed_cmd from fan_speed_user_input.
Revision: Rev. 01
Change: New Ver. 02 requirement
Source Baseline: Ver. 02
Change Rationale: Nil

## ACC-REQ-015: Automatic Mode Selection and Response (Functional)
When power_button == 1, mode_enabled == 1, and mode_selected == 2, the controller shall activate Automatic_Mode, set automatic_mode_enabled = 1, set fan_only_mode_enabled = 0 and cooling_mode_enabled = 0, and enable the cooling-control mechanism. The controller shall determine cooling demand automatically using the configured temperature logic. The controller shall select fan speed automatically when manual_fan_override == 0 and shall use manual fan-speed selection when manual_fan_override == 1.
Revision: Rev. 01
Change: New Ver. 02 requirement
Source Baseline: Ver. 02
Change Rationale: Nil

## ACC-REQ-016: Automatic Fan Speed Selection (Functional)
While Automatic_Mode is active and manual_fan_override == 0, the controller shall set automatic_fan_speed_enabled = 1 and determine fan_speed_cmd as follows:
If fan_on == 0, set fan_speed_cmd = 0.
If compressor_on == 1 and
temperature_error < medium_speed_threshold,
the controller shall set fan_speed_cmd = 1.
If compressor_on == 1 and
temperature_error >= medium_speed_threshold and
temperature_error < high_speed_threshold,
the controller shall set fan_speed_cmd = 2.
If compressor_on == 1 and
temperature_error >= high_speed_threshold,
the controller shall set fan_speed_cmd = 3.
Revision: Rev. 01
Change: New Ver. 02 requirement
Source Baseline: Ver. 02
Change Rationale: Nil

## ACC-REQ-017: Manual Fan Speed Selection and Override (Functional)
While Fan_Only_Mode or Cooling_Mode is active, or while Automatic_Mode is active with manual_fan_override == 1, the controller shall determine fan_speed_cmd from fan_speed_user_input.
If fan_on == 0, set fan_speed_cmd = 0.
If fan_speed_user_input == 0, set fan_speed_cmd = 1.
If fan_speed_user_input == 1, set fan_speed_cmd = 2.
If fan_speed_user_input == 2, set fan_speed_cmd = 3.
For any unsupported fan_speed_user_input, set fan_speed_cmd = 1 as the default fallback.
Revision: Rev. 01
Change: New Ver. 02 requirement
Source Baseline: Ver. 02
Change Rationale: Nil

## ACC-REQ-018: Compressor Lockout Status (Functional)
While the compressor minimum-OFF-time lockout is active, the controller shall set compressor_lockout = 1 and keep compressor_on = 0. After compressor_min_off_time has elapsed, the controller shall set compressor_lockout = 0. The controller shall also set compressor_lockout = 0 when cooling control is disabled, during Power_Off, and during Fault.
Revision: Rev. 01
Change: New Ver. 02 requirement
Source Baseline: Ver. 02
Change Rationale: Nil

## ACC-REQ-019: Fresh Cooling-Control Activation Lockout (Functional)
When cooling control transitions from disabled to enabled, the compressor mechanism shall start in minimum-OFF-time lockout with compressor_on = 0 and compressor_lockout = 1. Compressor activation shall not be permitted until compressor_min_off_time has elapsed and cooling demand is active.
Revision: Rev. 01
Change: New Ver. 02 requirement
Source Baseline: Ver. 02
Change Rationale: Nil
